module dang-kea-ha {
  yang-version 1.1;
  namespace "urn:dang:kea:ha";
  prefix dang-kea-ha;

  organization "dang project";
  contact "https://github.com/dcornejo/dang_plugins";
  description
    "Read-only operational state for Kea high-availability relationships.

     Kea's official DHCP server models carry HA hook configuration as an
     opaque JSON parameters leaf.  This companion model deliberately does
     not duplicate or replace that authoritative configuration.  It exposes
     the portable subset of the native status-get reply that dangd can verify
     across supported Kea installations.";

  revision 2026-09-28 {
    description
      "Expose the effective HA listener and active-peer transport security
       policy from the accepted Kea configuration.";
  }

  revision 2026-09-24 {
    description
      "Initial local-member HA operational state.";
  }

  typedef address-family {
    type enumeration {
      enum dhcpv4 {
        description "The relationship belongs to a Kea DHCPv4 daemon.";
      }
      enum dhcpv6 {
        description "The relationship belongs to a Kea DHCPv6 daemon.";
      }
    }
    description "Kea daemon family that owns an HA relationship.";
  }

  typedef transport-protection {
    type enumeration {
      enum plaintext {
        description "The dedicated HA channel does not use TLS.";
      }
      enum tls {
        description "The dedicated HA channel uses TLS.";
      }
    }
    description
      "Effective protection of one direction of Kea HA communication.";
  }

  container high-availability {
    config false;
    description
      "Live status for HA relationships on locally managed Kea daemons.
       Absence means the accepted daemon image has no HA hook relationship.";

    list relationship {
      key "address-family relationship-id";
      description
        "One relationship reported by a local Kea daemon.  The numeric ID is
         its position in Kea's status reply and is stable only until that
         daemon's accepted HA configuration changes.";

      leaf address-family {
        type address-family;
        description "Address family served by the reporting daemon.";
      }
      leaf relationship-id {
        type uint32;
        description "Zero-based relationship index in the native reply.";
      }
      leaf mode {
        type string;
        mandatory true;
        description
          "Kea HA mode, retained as text so newer native modes remain
           observable without a schema revision.";
      }

      container transport-security {
        presence
          "The accepted Kea configuration was available to resolve the
           effective transport policy.";
        description
          "Effective policy derived from the accepted native HA hook
           configuration. Certificate and key paths are intentionally not
           exposed.";
        leaf local-listener {
          type transport-protection;
          mandatory true;
          description
            "Protection used by the dedicated listener named by the local
             peer entry. Kea selects TLS from a complete effective
             trust-anchor, certificate, and private-key triplet rather than
             from the peer URL spelling.";
        }
        leaf client-certificates-required {
          when "../local-listener = 'tls'";
          type boolean;
          mandatory true;
          description
            "Whether the local TLS listener requires and verifies peer client
             certificates. Absent for a plaintext listener.";
        }
        leaf commands-restricted {
          type boolean;
          mandatory true;
          description
            "Whether the dedicated listener rejects commands not used by the
             HA hook.";
        }
        leaf active-remote {
          type transport-protection;
          description
            "Protection used for outbound communication to the singular
             active peer. Absent for passive-backup and for a local backup
             role without a singular active peer.";
        }
      }

      container local {
        description "Status of the locally managed member.";
        leaf server-name {
          type string;
          mandatory true;
          description "Kea name of the local member.";
        }
        leaf role {
          type string;
          mandatory true;
          description "Configured HA role reported for the local member.";
        }
        leaf state {
          type string;
          mandatory true;
          description "Current Kea HA state-machine state.";
        }
        leaf system-time {
          type string;
          description
            "UTC time used for the most recent clock-skew calculation, in
             Kea's native YYYY-MM-DD HH:MM:SS representation. Absent when no
             calculation has completed.";
        }
        leaf-list scope {
          type string;
          description "Current HA service scopes owned by the local member.";
        }
      }

      container remote {
        description
          "Last known status of the singular active relationship peer.
           Kea omits this container in passive-backup mode because a primary
           may have zero or multiple backup destinations.";
        leaf server-name {
          type string;
          mandatory true;
          description "Kea name of the remote member.";
        }
        leaf role {
          type string;
          mandatory true;
          description "Configured HA role reported for the remote member.";
        }
        leaf in-touch {
          type boolean;
          mandatory true;
          description "Whether Kea currently considers the peer reachable.";
        }
        leaf communication-interrupted {
          type boolean;
          mandatory true;
          description "Whether Kea reports interrupted peer communication.";
        }
        leaf age {
          type uint64;
          mandatory true;
          units "seconds";
          description "Age of the last information received from the peer.";
        }
        leaf analyzed-packets {
          type uint64;
          mandatory true;
          description
            "Packets directed to the peer that Kea has examined while
             monitoring interrupted communication.";
        }
        leaf clock-skew {
          type int64;
          units "seconds";
          description
            "Remote time minus local time at the most recent calculation.
             Absent until Kea has calculated clock skew.";
        }
        leaf connecting-clients {
          type uint64;
          mandatory true;
          description
            "Distinct clients observed attempting to contact the peer during
             interrupted-communication monitoring.";
        }
        leaf last-state {
          type string;
          mandatory true;
          description "Last peer state observed by the local member.";
        }
        leaf system-time {
          type string;
          description
            "Peer UTC time used for the most recent clock-skew calculation,
             in Kea's native YYYY-MM-DD HH:MM:SS representation. Absent until
             Kea has calculated clock skew.";
        }
        leaf unacked-clients {
          type uint64;
          mandatory true;
          description
            "Distinct clients considered unacknowledged by the peer.";
        }
        leaf unacked-clients-left {
          type uint64;
          mandatory true;
          description
            "Additional unacknowledged clients required before Kea enters
             partner-down state.";
        }
        leaf-list last-scope {
          type string;
          description "Last HA service scopes observed for the peer.";
        }
      }
    }
  }
}
