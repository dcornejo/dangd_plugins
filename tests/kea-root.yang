// Copyright 2026 David Cornejo
// SPDX-License-Identifier: Apache-2.0

module dang-kea-test-root {
  yang-version 1.1;
  namespace "urn:dang:kea:test-root";
  prefix dktr;

  import kea-dhcp4-server {
    prefix k4;
    revision-date 2026-06-24;
  }
  import kea-dhcp6-server {
    prefix k6;
    revision-date 2026-06-24;
  }

  revision 2026-08-26 {
    description "Compilation root for the external Kea plugin tests.";
  }
}
